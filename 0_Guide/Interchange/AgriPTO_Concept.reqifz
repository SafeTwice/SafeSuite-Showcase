# AgriPTO Concept Phase

# Specification: Functional_Safety_Concept

## PTO-FSC-000
Functional Safety Concept — Rear PTO
Safety goals and functional safety requirements per ISO 25119-2:2018, Clause 7. Every hazardous situation with AgPLr > QM maps to a safety goal; FSRs inherit the AgPLr of their goal. The selected combination of category, MTTFd, DC and SRL that achieves each AgPL is recorded in §3.
- Type: Title
- AgPL: QM
- Allocation: System
- Derived from: —
- Status: Verified

## —
1. Safety goals
- Type: Heading
- AgPL: QM
- Allocation: System
- Status: Verified

## PTO-SG-01
The PTO shall not engage unless a deliberate, valid operator engage command is present.
Safe state: clutch valve de-energised → clutch open, spring brake applied.
- Type: Requirement
- AgPL: AgPL d
- Allocation: System
- Derived from: PTO-HZ-01, -02
- Status: Verified
- Default -> R27
- Default -> R28

## PTO-SG-02
On a stop command or a stop condition the PTO shall be disengaged within 400 ms; the stop function has priority over any engage request (Annex F.3).
- Type: Requirement
- AgPL: AgPL c
- Allocation: System
- Derived from: PTO-HZ-03
- Status: Verified
- Default -> R29

## PTO-SG-03
The PTO shall not re-engage automatically: after power-up, after engine stall/restart, and after operator-presence loss, re-engagement requires a new deliberate command from the OFF position (manual reset, Annex F.4/F.5).
- Type: Requirement
- AgPL: AgPL c
- Allocation: System
- Derived from: PTO-HZ-04, -05
- Status: Verified
- Default -> R30
- Default -> R31

## PTO-SG-04
External (fender) engagement shall act only while the button is actively held, shall limit the shaft to creep speed (≤ 20 rpm), and shall never latch.
- Type: Requirement
- AgPL: AgPL b
- Allocation: System
- Derived from: PTO-HZ-06
- Status: Verified
- Default -> R32

## PTO-SG-05
The PTO shall keep the shaft inside the selected mode's speed envelope (≤ +10 %) and shall transfer torque through a controlled engagement ramp.
- Type: Requirement
- AgPL: AgPL b
- Allocation: System
- Derived from: PTO-HZ-07, -08
- Status: Verified
- Default -> R33
- Default -> R34

## —
2. Functional safety requirements
- Type: Heading
- AgPL: QM
- Allocation: System
- Status: Verified

## PTO-FSR-001
An engage command shall be accepted only as the valid two-step cab sequence (collar lifted, then switch pressed) with both switch contacts agreeing within 50 ms.
- Type: Requirement
- AgPL: AgPL d
- Allocation: Sensor / input
- Derived from: PTO-SG-01
- Status: Verified

## PTO-FSR-002
Engagement shall require independent agreement of two processing channels; no single E/E/PES fault shall energise the clutch valve.
- Type: Requirement
- AgPL: AgPL d
- Allocation: ECU / Hardware
- Derived from: PTO-SG-01
- Status: Verified

## PTO-FSR-003
At power-up the PTO output shall stay disabled until the start interlock passes: self-test complete, engage command absent, presence state valid (Annex F.2).
- Type: Requirement
- AgPL: AgPL d
- Allocation: ECU / Software
- Derived from: PTO-SG-01, -03
- Status: Verified

## PTO-FSR-004
A detected dangerous fault in the engage path shall force and latch the safe state; recovery only via manual reset with the fault cleared.
- Type: Requirement
- AgPL: AgPL d
- Allocation: System
- Derived from: PTO-SG-01
- Status: Verified

## PTO-FSR-005
A stop demand (switch OFF, either contact opening, presence loss > 1 s in mobile mode, monitor request) shall always be executable independently by each channel.
- Type: Requirement
- AgPL: AgPL c
- Allocation: ECU / Hardware
- Derived from: PTO-SG-02
- Status: Verified

## PTO-FSR-006
The reaction chain stop-demand → valve de-energised → clutch open → brake applied shall complete within 400 ms (response time per 25119-1, 3.38).
- Type: Requirement
- AgPL: AgPL c
- Allocation: System
- Derived from: PTO-SG-02
- Status: Verified

## PTO-FSR-007
The engaged state shall not be restored from memory: no engage state may survive a power cycle, brown-out or ECU reset.
- Type: Requirement
- AgPL: AgPL c
- Allocation: ECU / Software
- Derived from: PTO-SG-03
- Status: Verified

## PTO-FSR-008
Operator presence shall be monitored with plausibility (two contacts); in mobile operation, presence loss > 1 s shall trigger the stop chain. Stationary work mode requires a deliberate enable and engine-speed limit.
- Type: Requirement
- AgPL: AgPL c
- Allocation: Sensor / input
- Derived from: PTO-SG-03
- Status: Verified

## PTO-FSR-009
Fender engagement shall be accepted only with the cab switch OFF, shall run the shaft at creep (≤ 20 rpm, jog pulses), and shall stop within 200 ms of button release.
- Type: Requirement
- AgPL: AgPL b
- Allocation: System
- Derived from: PTO-SG-04
- Status: Verified

## PTO-FSR-010
Fender-button stuck-at conditions shall be detected (release supervision) and shall inhibit external engagement.
- Type: Requirement
- AgPL: AgPL b
- Allocation: Sensor / input
- Derived from: PTO-SG-04
- Status: Verified

## PTO-FSR-011
Shaft speed shall be supervised against the selected mode; a sustained excursion beyond +10 % shall raise a warning and trigger a controlled disengage (degraded stop).
- Type: Requirement
- AgPL: AgPL b
- Allocation: ECU / Software
- Derived from: PTO-SG-05
- Status: Verified

## PTO-FSR-012
The selected speed mode shall be read redundantly (coded lever + measured engine/shaft ratio) and mismatches shall inhibit engagement.
- Type: Requirement
- AgPL: AgPL b
- Allocation: Sensor / input
- Derived from: PTO-SG-05
- Status: Verified

## PTO-FSR-013
Engagement shall modulate clutch pressure along a ramp (≤ 2.0 s, slip supervised); step engagement shall be prevented.
- Type: Requirement
- AgPL: AgPL b
- Allocation: ECU / Software
- Derived from: PTO-SG-05
- Status: Verified

## PTO-FSR-014
Detected faults and degraded modes shall be indicated to the operator (lamp + buzzer via cluster); indication is QM and shall not be relied on for any safety function.
- Type: Requirement
- AgPL: QM
- Allocation: System
- Derived from: PTO-SG-02
- Status: Verified

## PTO-FSC-SEL
3. Achieving the AgPL — selected combination (25119-2, 7.3.5)
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Figure 1 — category/MTTFd/DC/SRL combinations; the PTO-ECU selection for AgPL d is ringed
Selected for the AgPL d engage/stop chain: Category 3 (dual channel, cross-monitoring), MTTFd medium per channel (target ≥ 10 y, achieved values in 4_Hardware/Reliability_Metrics), DC medium (target ≥ 60 %, achieved by the diagnostic set D1–D5), SRL 2 software, CCF score ≥ 65 (achieved 85, Annex D scoring below). AgPL b/c functions ride on the same architecture and inherit its integrity.
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Figure 2 — CCF scoring (Annex D)
- Type: Info
- AgPL: AgPL d
- Allocation: System
- Derived from: —
- Status: Verified

## PTO-FSC-EXT
4. External measures and interfaces to other technologies
The spring-applied PTO brake and the clutch return spring are mechanical measures: de-energising the valve reaches the safe state without any E/E/PES action (de-energise-to-safe). The master shield and shaft guards are machine-level measures per ISO 4254-1 (outside the UoO). Failures of hydraulic and mechanical parts are context events in the FTA, not SRP/CS failures (25119-1, 6.2.2).
- Type: Info
- AgPL: QM
- Allocation: System
- Derived from: —
- Status: Verified

# Specification: HARA

## R25
Hazard Analysis and Risk Assessment — Rear PTO
HARA per ISO 25119-2:2018, Clause 6, for the faulted UoO (malfunctioning behaviour of the PTO control). Participants: E. Vidal (safety), H. Larsen (systems), C. Reid (field/operator view), P. Ferraro (hardware), G. Hoffmann (assessor, observer). Harm to persons only; property-only outcomes are recorded as QM.
Method: system states and transitions per the state flowchart in the Technical Safety Concept; for every malfunction the relevant operating situations were rated. Where frequency and duration methods give different exposure classes, the higher class is used (6.3.5).
- HazID: PTO-HZ-000
- Severity: S0
- Exposure: E0
- Controllability: C0
- AgPLr: QM
- Safety goal: —
- Safe state: None (QM)

## R26
Risk graph
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Figure 1 — AgPLr determination (ISO 25119-2 Fig. 1); rated cells of this HARA are ringed
- HazID: —
- Severity: S0
- Exposure: E0
- Controllability: C0
- AgPLr: QM
- Safety goal: —
- Safe state: None (QM)

## R27
Unintended PTO engagement while a person is at the implement or driveline (coupling the shaft, fitting the guard, adjusting the machine; engine running, PTO commanded OFF).
Harm scenario: clothing or limb caught by the engaging shaft/implement intake — entanglement injuries.
- HazID: PTO-HZ-01
- Severity: S3
- Exposure: E3
- Controllability: C3
- AgPLr: AgPL d
- Safety goal: PTO-SG-01
- Safe state: Clutch open + PTO brake
- Rationale: S3: entanglement by a 540 rpm shaft is life-threatening, survival uncertain (accident statistics for PTO entanglement).
  E3: by the frequency method — a person is in the driveline zone with the engine running more than once per month on every livestock or mixed farm (coupling is part of nearly every implement use). Duration method would give E2; the higher class governs (6.3.5).
  C3: once engagement starts, a person in contact with the shaft cannot avoid harm.

## R28
Unintended engagement with a bystander next to a stationary implement (slurry pump, auger) — person feeding or clearing the machine while PTO is OFF.
- HazID: PTO-HZ-02
- Severity: S3
- Exposure: E2
- Controllability: C3
- AgPLr: AgPL c
- Safety goal: PTO-SG-01
- Safe state: Clutch open + PTO brake
- Rationale: Same failure as PTO-HZ-01, different situation: bystander presence at a parked, powered machine is less frequent (E2: 0.1–1 % of operating time). Bounded by PTO-HZ-01; SG-01 carries the higher AgPLr d.

## R29
PTO fails to disengage on operator stop command. Typical scenario: baler pickup blocks, operator commands PTO OFF and dismounts to clear it while the shaft is in fact still driven.
- HazID: PTO-HZ-03
- Severity: S3
- Exposure: E3
- Controllability: C2
- AgPLr: AgPL c
- Safety goal: PTO-SG-02
- Safe state: Clutch open + PTO brake
- Rationale: S3: intake/pickup entanglement.
  E3: intervening at the implement after a stop command is routine (blockages, wrapping, checking) — more than once per month.
  C2: mostly controllable — a still-turning shaft or implement is visible and audible before contact for >90 % of persons (trained operators check); not C1 because noise/enclosure can mask it, not C3 because the cue exists. Season field data (C. Reid: 41 logged interventions, 2 near-miss reports) confirms the shaft-still-turning cue is used by operators; the reports are folded into the operator-manual warnings (10.4.5).

## R30
PTO does not shut off when the operator leaves the seat during mobile work (operator-presence function fails), operator walks to the still-driven implement.
- HazID: PTO-HZ-04
- Severity: S3
- Exposure: E2
- Controllability: C3
- AgPLr: AgPL c
- Safety goal: PTO-SG-03
- Safe state: Clutch open + PTO brake
- Rationale: S3 as above. E2: leaving the seat with the PTO running (outside the stationary-work exception) is occasional. C3: the operator believes the presence function has shut the PTO off — no cue prompts a check before contact.

## R31
Automatic re-engagement at key-on / engine restart with the cab switch still latched from the previous session; person at the implement during the morning start.
- HazID: PTO-HZ-05
- Severity: S3
- Exposure: E2
- Controllability: C3
- AgPLr: AgPL c
- Safety goal: PTO-SG-03
- Safe state: Clutch open + PTO brake
- Rationale: Restart with a latched switch is a classic PTO accident pattern. E2 by frequency (restarts with implement attached and person nearby: >1/year, <1/month for the hazardous combination). C3: no warning precedes the engagement.

## R32
Fender jog latches ON or fails to stop on button release — the operator standing at the fender is within arm's reach of the turning shaft end.
- HazID: PTO-HZ-06
- Severity: S3
- Exposure: E2
- Controllability: C2
- AgPLr: AgPL b
- Safety goal: PTO-SG-04
- Safe state: Clutch open + PTO brake
- Rationale: S3: shaft-end entanglement. E2: fender jog is used during coupling only. C2: the user's hand is on the button and the jog speed is limited to creep (≤ 20 rpm) — releasing/stepping back succeeds for >90 %; not C1 because the person is inside the danger zone by definition.

## R33
Shaft overspeed: 1000-mode speed delivered while a 540-only implement is attached (wrong internal mode or wrong ratio supervision). Implement overspeed → break-up, ejected parts hitting a bystander.
- HazID: PTO-HZ-07
- Severity: S3
- Exposure: E1
- Controllability: C3
- AgPLr: AgPL b
- Safety goal: PTO-SG-05
- Safe state: Warning + degraded
- Rationale: S3 for a struck bystander (fragments). E1: requires simultaneous mode malfunction, 540-only implement, near-field bystander — rare (<1/year). C3: no avoidance once break-up occurs. Driver in cab rated separately S2/E2/C3 → b; the governing class stays b.
  Safe state: warning + controlled disengage (degraded); an abrupt cut at full load is itself hazardous, see PTO-TSR-016.

## R34
Engagement without torque ramp (full pressure step): driveline shock can shear shaft bolts / yoke, fragments near the hitch area.
- HazID: PTO-HZ-08
- Severity: S2
- Exposure: E2
- Controllability: C3
- AgPLr: AgPL b
- Safety goal: PTO-SG-05
- Safe state: Warning + degraded
- Rationale: S2: fragment energies at engagement speed are lower than the break-up case (severe, survival probable). E2: engagement happens every use, but the harm needs a person beside the hitch at that moment. C3: no reaction possible.

## R35
PTO state indication wrong (cluster lamp shows OFF while shaft is driven). Contributes to PTO-HZ-03-type scenarios; standalone harm requires additional failures.
- HazID: PTO-HZ-09
- Severity: S2
- Exposure: E1
- Controllability: C2
- AgPLr: QM
- Safety goal: —
- Safe state: None (QM)
- Rationale: Indication is a supporting function: harm needs the primary channel to have failed as well. Rated standalone S2/E1/C2 → QM; developed under quality measures, no AgPL. It is nevertheless supervised (CAN alive counter) because of its contribution to controllability in PTO-HZ-03.

## R36
Unintended engagement during road transport with no implement attached (stub shaft turns under its guard).
- HazID: PTO-HZ-10
- Severity: S1
- Exposure: E2
- Controllability: C2
- AgPLr: QM
- Safety goal: —
- Safe state: None (QM)
- Rationale: The guarded stub shaft without an implement exposes no person; residual risk limited to the missing-guard misuse case → S1. QM; the master guard requirement itself is mechanical (ISO 4254-1) and outside the UoO.

## R37
Result
Highest requirement: AgPL d (PTO-HZ-01). Safety goals PTO-SG-01 … PTO-SG-05 are derived in the Functional Safety Concept; every hazardous situation with AgPLr > QM is covered by exactly one safety goal. This HARA is reworked on any change of the UoO scope (impact analysis per ISO 25119-4 Clause 11).
- HazID: —
- Severity: S0
- Exposure: E0
- Controllability: C0
- AgPLr: QM
- Safety goal: → FSC
- Safe state: None (QM)

# Specification: Item_Definition_UoO

## PTO-UOO-000
Concept of the UoO — Rear PTO control system
Unit of observation per ISO 25119-2:2018, Clause 5. Machine: Ager Dynamics T6100 tractor platform (82–125 kW). The UoO is the E/E/PES part of the rear PTO control: PTO-ECU 200 with its sensors, operator controls and the clutch valve output stage. The wet clutch pack, spring-applied PTO brake, gearbox and stub shaft are mechanical context — their failures are outside ISO 25119 scope but appear in the FTA as context events.
- Type: Title
- Status: Agreed

## PTO-UOO-001
1. System overview
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Figure 1 — UoO boundary and actuation context
- Type: Info
- Status: Agreed

## PTO-UOO-002
2. Functions of the UoO
F1 Engage/disengage the rear PTO on operator command (cab switch).
F2 External engage jog from either fender (coupling aid, hold-to-run).
F3 Select and supervise the PTO speed mode (540 / 540E / 1000 rpm).
F4 Automatic shut-off on operator-presence loss during mobile work; stationary-mode exception with deliberate confirmation.
F5 Controlled engagement ramp (limit driveline shock).
F6 Status indication to the cluster (lamp, buzzer) — QM.
Historical basis: the function set and its safety behaviour follow common European tractor practice and the machine-level requirements of ISO 26322 / ISO 4254-1 for PTO controls.
- Type: Info
- Status: Agreed

## PTO-UOO-003
3. Limits and interfaces
Interface | Direction | Type | Characteristics | Cab PTO switch | in | 2 × discrete | lift-collar guarded rocker; NO + NC contacts, 12 V wetted | Fender buttons L / R | in | discrete | momentary, guarded housing, hold-to-run only | Operator presence (seat) | in | discrete ×2 | seat switch, second contact for plausibility | Speed-mode selector | in | analog coded | 540 / 540E / 1000, resistor-coded lever position | PTO shaft speed | in | frequency | inductive pickup on 58-tooth wheel, 0.3–3 kHz | Engine speed (CAN) | in | CAN 250k | J1939 EEC1, 20 ms cycle, timeout supervised | Clutch valve | out | PWM 12 V | solenoid 2.2 Ω; de-energised = clutch OPEN (brake applied) | Valve current sense | in | analog | shunt + amplifier, 0–2 A, read by both MCUs | Clutch pressure switch | in | discrete | closes ≥ 14 bar (clutch filled), plausibility only | Cluster indication | out | CAN 250k | PTO state lamp + buzzer request (QM function)
- Type: Info
- Status: Agreed

## PTO-UOO-004
4. Ambient conditions and sources of stress (5.3.3)
Environment class per ISO 15003: cab-mounted ECU, −25 °C … +70 °C ambient, vibration 5 g (10–500 Hz), humidity 95 % non-condensing, IP54 at the connector zone. Electrical: 12 V system, cranking dips to 6 V, load dump per ISO 7637-2 pulse 5a (clamped), reverse polarity −14 V. EMC per ISO 14982 (agricultural machinery).
Stress sources considered: interaction with the hitch ECU (shared CAN), chemical exposure (fertiliser dust, washing), operator misuse (jump start, welding on frame), harness chafing near the fender buttons, and assembly errors (connector cross-mating is excluded by keying — fault exclusion FE-1, justified in the FMEA).
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Figure 2 — mission profile used for the IEC/TR 62380 reliability prediction (SafeFIT)
- Type: Info
- Status: Agreed

## PTO-UOO-005
5. Additional determinations (5.3.4)
New development: the PTO-ECU 200 replaces the relay-based PTO control of the T5 series (field history 11 years, 41 000 units — used as proven-in-use reference for the valve and clutch, not for the new electronics). Reliability input data: IEC/TR 62380 with the mission profile of Figure 2. Tools: SafeSuite (this project), SafeFIT (FIT prediction), SafeFMEA, SafeTree (FTA). Staff qualification per Safety Plan §2.
- Type: Info
- Status: Agreed
